HorusBinaryV3 DEFINITIONS ::= BEGIN

BitFlags ::= SEQUENCE {
    b0 [0] EXPLICIT BOOLEAN,
    b1 [1] EXPLICIT BOOLEAN,
    b2 [2] EXPLICIT BOOLEAN,
    b3 [3] EXPLICIT BOOLEAN,
    b4 [4] EXPLICIT BOOLEAN,
    b5 [5] EXPLICIT BOOLEAN,
    b6 [6] EXPLICIT BOOLEAN,
    b7 [7] EXPLICIT BOOLEAN
}

CustomFieldValues ::= CHOICE {
        -- prefixed with horus otherwise c codegen is bad

        -- allows base64 - if you were crazy enough
        horusStr  [0] EXPLICIT IA5String (FROM("abcdefghijklmnopqrstuvwxyzABCDEFGHIJKLMNOPQRSTUVWXYZ0123456789_ +/=-.")), 
        horusInt  [1] EXPLICIT SEQUENCE(SIZE(1..4)) OF INTEGER,
        horusReal [2] EXPLICIT SEQUENCE(SIZE(1..4)) OF REAL,

        -- we could use a bit string here, but it packs down the same so we may as well make it easier on ourselves to process
        horusBool [3] EXPLICIT BitFlags
}

AdditionalSensorType ::= SEQUENCE {
        -- adding a name will add 
        -- overhead but means anyone can find out what the sensor does
        name            [0] EXPLICIT IA5String (FROM("abcdefghijklmnopqrstuvwxyz0123456789-")^SIZE (1..20)) OPTIONAL, 
        
        -- values are optional as we may want to send a packet without values and only names
        values          [1] EXPLICIT CustomFieldValues OPTIONAL
}

-- we limit to 4 additional sensor types to lower out used bits
AdditionalSensors ::= SEQUENCE(SIZE(1..4)) OF AdditionalSensorType

TemperatureSensors ::= SEQUENCE {
    internal [0] EXPLICIT INTEGER (-1023..1023) OPTIONAL,  -- tenths C
    external [1] EXPLICIT INTEGER (-1023..1023) OPTIONAL,  -- tenths C
    custom1   [2] EXPLICIT INTEGER (-1023..1023) OPTIONAL, -- tenths C
    custom2   [3] EXPLICIT INTEGER (-1023..1023) OPTIONAL  -- tenths C
}

MilliVoltSensors ::= SEQUENCE {
    battery  [0] EXPLICIT INTEGER (0..16383) OPTIONAL, -- millivolts
    solar    [1] EXPLICIT INTEGER (0..16383) OPTIONAL, -- millivolts
    custom1  [2] EXPLICIT INTEGER (0..16383) OPTIONAL, -- millivolts
    custom2   [3] EXPLICIT INTEGER (0..16383) OPTIONAL -- millivolts
}

Telemetry ::= SEQUENCE {
    -- required fields
    payloadCallsign     [1] EXPLICIT IA5String (FROM("-/abcdefghijklmnopqrstuvwxyzABCDEFGHIJKLMNOPQRSTUVWXYZ0123456789")^SIZE (1..15)),
    sequenceNumber      [2] EXPLICIT INTEGER (0..65535),

    -- these are common fields that are required to transmit
    -- however if the data is missing, transmit 0,0 for lat/lon and timeofdayseconds -1
    timeOfDaySeconds        [3] EXPLICIT INTEGER (-1..86400), -- seconds since
                                                               -- 00:00 UTC - highly recommended to have time of day seconds in very transmissions
    latitude                [4] EXPLICIT INTEGER (-9000000..9000000),    -- fixed point, x100000
    longitude               [5] EXPLICIT INTEGER (-18000000..18000000),  -- fixed point, x100000


        -- bits - these mostly came from rs41 ng                   - set to zero if not in use
    safeMode                   [6] EXPLICIT BOOLEAN OPTIONAL,
    powerSave                  [7] EXPLICIT BOOLEAN OPTIONAL,
    gpsLock                    [8] EXPLICIT BOOLEAN OPTIONAL,

    -- highly recommended field
    altitudeMeters          [9] EXPLICIT INTEGER (-1000..50000), -- meters - set to -1000 if invalid

    -- additional extra sensors
    extraSensors            [10] EXPLICIT AdditionalSensors OPTIONAL,
 
    -- additional fields that would be unlikely to need to be sequences
    velocityHorizontalKilometersPerHour   [11] EXPLICIT INTEGER (0..512)    OPTIONAL, -- km/hr
    gnssSatellitesVisible                 [12] EXPLICIT INTEGER (0..31)     OPTIONAL, -- note that the
                                                  -- power mode can now be expressed in bits below
    ascentRateCentimetersPerSecond       [13] EXPLICIT INTEGER (-32767..32767)                    OPTIONAL, -- cm/s
    pressurehPa                          [14] EXPLICIT INTEGER (0..1200)     OPTIONAL, -- hPa


    -- additional but fairly common fields so we make them explicit
    temperatureCelsius         [15] EXPLICIT TemperatureSensors   OPTIONAL, -- C
    humidityPercentage         [16] EXPLICIT INTEGER (0..100)     OPTIONAL, -- %
    milliVolts                 [17] EXPLICIT MilliVoltSensors     OPTIONAL, -- 
    counts                     [18] EXPLICIT SEQUENCE(SIZE(1..8)) OF INTEGER OPTIONAL,
    


    -- binary data
    customData                 [19] EXPLICIT OCTET STRING OPTIONAL,
    ...  -- this is an extension marker - it lets us add fields
}
END
